module hex_input {
  namespace "http://rogvall.se/hex";
  prefix "hex";
  container config {
    leaf digital {
      type boolean;
      description "Allow digital input signals.";
      default true;
    }
    leaf analog {
      type boolean;
      description "Allow analog input signals.";
      default true;
    }
    leaf encoder {
      type boolean;
      description "Allow encoder input signals.";
      default true;
    }
    leaf rifd {
      type boolean;
      description "Allow rfid input signals.";
      default true;
    }
    leaf analog_to_digital {
      type boolean;
      description "Convert analog to digital signals.";
      default false;
    }
    leaf digital_to_analog {
      type boolean;
      description "Convert digital to analog signals.";
      default false;
    }
    leaf on_only {
      type boolean;
      description "Accept digital on signals.";
      default false;
    }
    leaf off_only {
      type boolean;
      description "Accept digital off signals.";
      default false;
    }
    leaf springback {
      type boolean;
      description "Input is from a 'springback' button.";
      default false;
    }
    leaf invert {
      type boolean;
      description "Digital input is inverted.";
      default false;
    }
    leaf push_encoder {
      type boolean;
      description "Activate push encoder functionallity.";
      default false;
    }
    leaf inc_encoder {
      type boolean;
      description "Push encoder that only increaments.";
      default false;
    }
    leaf dec_encoder {
      type boolean;
      description "Push encoder that only decrements.";
      default false;
    }
    leaf encoder_ival {
      type uint32;
      description "Push encoder update interval.";
      default 250;
    }
    leaf encoder_pause {
      type uint32;
      description "Push encoder direction switch timeout.";
      default 3000;
    }
    leaf encoder_step {
      type uint32;
      description "Push encoder update step.";
      default 1;
    }
    leaf analog_delta {
      type uint32;
      description "Analog delta value.";
      default 1;
    }
    leaf analog_trigger {
      type bits {
        bit 'upper-limit-exceeded' {
          position 0;
        }
        bit below_lower_limit {
          position 1;
        }
        bit 'changed-by-more-than-delta' {
          position 2;
        }
        bit 'changed-by-more-than-negative-delta' {
          position 3;
        }
        bit 'changed-by-more-than-positive-delta' {
          position 4;
        }
      }
    }
    leaf analog_negative_delta {
      type uint32;
      description "Analog negative delta value.";
      default 1;
    }
    leaf analog_positive_delta {
      type uint32;
      description "Analog positive delta value.";
      default 1;
    }
    leaf analog_max_frequency {
      type decimal64 {
        fraction-digits 6;
      }
      description "Analog max output frequency.";
      default 0;
    }
    leaf analog_lower_limit {
      type int32;
      description "Analog lower limit.";
      default 0;
    }
    leaf analog_upper_limit {
      type int32;
      description "Analog upper limit.";
      default 65535;
    }
    leaf analog_min {
      type int32;
      description "Analog min value.";
      default 0;
    }
    leaf analog_max {
      type int32;
      description "Analog max value.";
      default 65535;
    }
    leaf analog_offs {
      type int32;
      description "Analog offset value.";
      default 0;
    }
    leaf analog_scale {
      type decimal64 {
        fraction-digits 6;
      }
      description "Analog offset value.";
      default 1.0;
    }
    leaf rfid_match {
      type uint32;
      default 0;
    }
    leaf rfid_mask {
      type uint32;
      default 0;
    }
    leaf rfid_match_to_digital {
      type boolean;
      default false;
    }
    list output {
      key channel;
      leaf channel {
        type uint8 {
          range 1..254;
        }
      }
      leaf target {
        type string;
        default value;
      }
    }
  }
}
